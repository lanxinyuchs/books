--
-- The Ericsson IP Address Change MIB
--
-- Copyright (c) 2017 by Ericsson AB.
-- All rights reserved.
--
-- This MIB Module is an Ericsson-wide SNMP
-- interface for the change of ip address of a node.
-- See the module identity description below.
--
-- Authors:
-- Kieran A McCarthy
--
--===================================================
-- TODO:
--  - Allocate product number in PRIM
--
-- The MIB passes simple web at level 6
-- (https://www.simpleweb.org/ietf/mibs/validate/)
--
ERICSSON-CHANGEIPADDRESS-MIB DEFINITIONS ::= BEGIN

IMPORTS
        MODULE-IDENTITY, OBJECT-TYPE, NOTIFICATION-TYPE,
        Integer32
                FROM SNMPv2-SMI
        TEXTUAL-CONVENTION
                FROM SNMPv2-TC
        InetAddress, InetAddressType
                FROM INET-ADDRESS-MIB
        -- SnmpAdminString
        --        FROM SNMP-FRAMEWORK-MIB
        ericssonModules
                FROM ERICSSON-TOP-MIB
        -- IANAItuEventType
        --        FROM IANA-ITU-ALARM-TC-MIB
        -- snmpTargetBasicGroup
        --        FROM SNMP-TARGET-MIB
        -- snmpNotifyGroup
        --        FROM SNMP-NOTIFICATION-MIB
        OBJECT-GROUP, NOTIFICATION-GROUP, MODULE-COMPLIANCE
                FROM SNMPv2-CONF;

ericssonChangeIPAddressMIB MODULE-IDENTITY
        LAST-UPDATED "201702061400Z"
        ORGANIZATION "Ericsson AB"
        CONTACT-INFO
                "Email: kieran.a.mccarthy@ericsson.com"
        DESCRIPTION
                "This MIB Module is an Ericsson-wide SNMP
                interface for the change of ip address of a node. It 
                describes the notification used to send a new ip address
                for a node to a management system, and a mechanism
                for a management system to acknowledge the successful 
                processing of this message. 

                The agent is expected to repeatedly send the ip address 
                change message until reception has been acknowleged by 
                the management system through the notification mechanism
                in this MIB.
                
		See eriChangeIPAddressStatus for details.

		The frequency at which to send change ip address messages is
		implementation specific, but must not be more often
		than one message per minute or more frequent than one message
		per hour.

                MIB Product number in GASK: n/nnn nn-CXC nnn nnnn, Rev x"
 
        REVISION "201702061400Z"
        DESCRIPTION
                "Initial version of this MIB module."

        ::= { ericssonModules 6 }

--===================================================
-- Groups
--===================================================

eriChangeIPAddressObjects         OBJECT IDENTIFIER ::= { ericssonChangeIPAddressMIB 1 }
eriChangeIPAddressNotifications   OBJECT IDENTIFIER ::= { ericssonChangeIPAddressMIB 2 }
eriChangeIPAddressMIBCompliances  OBJECT IDENTIFIER ::= { ericssonChangeIPAddressMIB 3 }

-- The following is needed for SMIv1 backward compatibility,
-- see section 8.5 of RFC 2578.
eriChangeIPAddressNotifsPrefix    OBJECT IDENTIFIER ::= { eriChangeIPAddressNotifications 0 } 



--====================================================
-- Notification objects
--
-- These are the 'attributes' of all possible
-- ChangeIPAddress messages defined by this MIB.
-- They are grouped as securitymandatory objects
-- and optional objects.
--====================================================

--====================================================
-- ChangeIPAddress inform objects          
--
-- These are the attributes used in the ChangeIPAddress inform.
--====================================================

EriChangeIPAddressText16 ::= TEXTUAL-CONVENTION
    DISPLAY-HINT "16a"
    STATUS      current
    DESCRIPTION "ASCII string data of max length 16 octets."
    SYNTAX      OCTET STRING(SIZE(0..16))

EriChangeIPAddressIdValueText ::= TEXTUAL-CONVENTION
    DISPLAY-HINT "400a"
    STATUS      current
    DESCRIPTION "ASCII string data of max length 400 octets."
    SYNTAX      OCTET STRING(SIZE(0..400))
-- 3GPP TS 32.300 v9.0.0 chapter 7.4 states max DN length to 400 octets.

EriChangeIPAddressShortValueText ::= TEXTUAL-CONVENTION
    DISPLAY-HINT "50a"
    STATUS      current
    DESCRIPTION "ASCII string data of max length 50 octets."
    SYNTAX      OCTET STRING(SIZE(0..50))

EriChangeIPAddressAckValue ::= TEXTUAL-CONVENTION
    DISPLAY-HINT "x"
    STATUS      current
    DESCRIPTION "Change IP address acknowledgement value"
    SYNTAX      Integer32


EriChangeIPAddressChecksumValue ::= TEXTUAL-CONVENTION
    DISPLAY-HINT "x"
    STATUS      current
    DESCRIPTION "32 bit checksum value"
    SYNTAX      Integer32

    EriChangeIPAddressRemainingRetriesValue ::= TEXTUAL-CONVENTION
    DISPLAY-HINT "x"
    STATUS      current
    DESCRIPTION "32 bit retries value"
    SYNTAX      Integer32


eriChangeIPAddressNodeIdValue     OBJECT-TYPE
    SYNTAX      EriChangeIPAddressIdValueText      -- 0..400 oct
    MAX-ACCESS  accessible-for-notify
    STATUS      current
    DESCRIPTION
        "The name of the node.
        It would correspond to the node RDN value (e.g. corresponding to ManagedElement.networkManagedElementId)"
    ::= { eriChangeIPAddressObjects 1 }


eriChangeIPAddressChecksum  OBJECT-TYPE
    SYNTAX      EriChangeIPAddressChecksumValue   -- 32bit (4 oct)
    MAX-ACCESS  accessible-for-notify
    STATUS      current
    DESCRIPTION
        "The security check sum (SCC) calculated by the NE.
        This is optional to support dynamic ip address changes 
        initiated outside the management system"
    ::= { eriChangeIPAddressObjects 2 }

eriChangeIPAddressChecksumVersion  OBJECT-TYPE
    SYNTAX      EriChangeIPAddressText16   -- 0..16 oct
    MAX-ACCESS  accessible-for-notify
    STATUS      current
    DESCRIPTION
        "The version of the SCC. Only one version is currently supported, represented by the literal '1.0'"
    ::= { eriChangeIPAddressObjects 3 }

eriChangeIPAddressNewNodeOamIpAddressType     OBJECT-TYPE
    SYNTAX      InetAddressType
    MAX-ACCESS  accessible-for-notify
    STATUS      current
    DESCRIPTION
    "The type of address used for the new oam ip address - IPv4, IPv6, etc "
    REFERENCE "Revision 200006080000Z of the inetAddressMIB (RFC 4001)"
    ::= { eriChangeIPAddressObjects 4 }

eriChangeIPAddressNewNodeOamIpAddress     OBJECT-TYPE
    SYNTAX      InetAddress
    MAX-ACCESS  accessible-for-notify
    STATUS      current
    DESCRIPTION
        "The new oam ip address"
    REFERENCE "Revision 200006080000Z of the inetAddressMIB (RFC 4001)"
    ::= { eriChangeIPAddressObjects 5 }
    
eriChangeIPAddressAckFdn     OBJECT-TYPE
    SYNTAX      EriChangeIPAddressIdValueText      -- 0..400 oct
    MAX-ACCESS  accessible-for-notify
    STATUS      current
    DESCRIPTION
        "The FDN of the MO used to acknowledge the successful 
        setting of the ip address in the management system.
        The management system will set the attribute defined in 
        eriChangeIPAddressAckAttributeName on this MO FDN"
    ::= { eriChangeIPAddressObjects 6 }

eriChangeIPAddressAckAttributeName     OBJECT-TYPE
    SYNTAX      EriChangeIPAddressShortValueText      -- 0..50 oct
    MAX-ACCESS  accessible-for-notify
    STATUS      current
    DESCRIPTION
        "The name of the attribute used to acknowledge the successful 
        setting of the ip address in the management system. This attribute 
        must exist in the Mo defined by eriChangeIPAddressAckFdn.
        For example this name could be something like 'ipAddressChangeStatus'.
        This attribute must be of type Integer"
    ::= { eriChangeIPAddressObjects 7 }

eriChangeIPAddressAckAttributeValue     OBJECT-TYPE
    SYNTAX      EriChangeIPAddressAckValue
    MAX-ACCESS  accessible-for-notify
    STATUS      current
    DESCRIPTION
        "The value of the attribute used to acknowledge the successful 
        setting of the ip address in the management system.
        The value must be an integer value to correlate with attribute defined in
        eriChangeIPAddressAckAttributeName"
    ::= { eriChangeIPAddressObjects 8 }

eriChangeIPAddressRemainingRetries     OBJECT-TYPE
    SYNTAX      EriChangeIPAddressRemainingRetriesValue      -- 0..4 oct
    MAX-ACCESS  accessible-for-notify
    STATUS      current
    DESCRIPTION
        "The number of retries remaining.
        The remote entity (node) may retry as many times as it wishes.
        This value will specify how many further retries are remaining 
        after this one.  For example, if this value is 0 then the 
        comsumer/receiver of this snmp message can assume this is the 
        final attempt to change the ip address.  The receiver may
        decide to take an appropriate action (such as raise an alarm 
        for example) if this final attempt to change address fails.
        If this parameter is not supplied it is assumed that the 
        remaining retries value is 0 (meaning that the management
        system may take appropriate action on last ip address 
        change attempt)"
    ::= { eriChangeIPAddressObjects 9 }

--====================================================
-- Notifications and notification specific objects.
--
-- This is the generic ChangeIPAddress message that
-- any node may send to a node management system.
--
--====================================================

eriChangeIPAddressEvent NOTIFICATION-TYPE
       OBJECTS {
              eriChangeIPAddressNodeIdValue,                  -- 0..400   Mandatory
              eriChangeIPAddressChecksum,                     -- 4        Optional
              eriChangeIPAddressChecksumVersion,              -- 0..16    Optional
              eriChangeIPAddressNewNodeOamIpAddressType,      -- 1        Mandatory
              eriChangeIPAddressNewNodeOamIpAddress,          -- 0..256   Mandatory
              eriChangeIPAddressAckFdn,                       -- 0..400   Mandatory
              eriChangeIPAddressAckAttributeName,             -- 0..50    Mandatory
              eriChangeIPAddressAckAttributeValue,            -- 0..50    Mandatory
              eriChangeIPAddressRemainingRetries              -- 4        Optional
       }
       STATUS   current                           
       DESCRIPTION
           "This is the ChangeIPAddress notification sent from a
           node supporting dynamic or changing ip addresses.
           It is asumed that some data has been prepared in an
           OSS to recognise the node by the ID."
       ::= { eriChangeIPAddressNotifsPrefix 1 }

--=============================================
--==Textual conventions for notification data==
--=============================================



--=============================================
-- Comformance Information - group definitions
--=============================================

eriChangeIPAddressMIBComplianceGroups	OBJECT IDENTIFIER ::= { eriChangeIPAddressMIBCompliances 1 }


eriChangeIPAddressEventContentGroup OBJECT-GROUP
    OBJECTS	{      
        eriChangeIPAddressNodeIdValue,               -- Mandatory       
        eriChangeIPAddressChecksum,                  -- Optional
        eriChangeIPAddressChecksumVersion,           -- Optional
        eriChangeIPAddressNewNodeOamIpAddressType,   -- Mandatory
        eriChangeIPAddressNewNodeOamIpAddress,       -- Mandatory
        eriChangeIPAddressAckFdn,                    -- Mandatory
        eriChangeIPAddressAckAttributeName,          -- Mandatory
        eriChangeIPAddressAckAttributeValue,         -- Mandatory
        eriChangeIPAddressRemainingRetries           -- Optional
    		}
   STATUS	current
   DESCRIPTION  "Mandatory objects to include in the events"
       ::= {eriChangeIPAddressMIBComplianceGroups 1}

eriChangeIPAddressEventGroup NOTIFICATION-GROUP
    NOTIFICATIONS {
    			eriChangeIPAddressEvent
		  }
   STATUS	current
   DESCRIPTION  "Mandatory events"
       ::= {eriChangeIPAddressMIBComplianceGroups 2}


--=============================================
-- Comformance Information - compliance
--=============================================

ericssonChangeIPAddressMIBBasicCompliance MODULE-COMPLIANCE
    STATUS      current
    DESCRIPTION "Compliance descriptions - mandatory groups and optional groups"
    MODULE      -- compliance for this MIB module
    MANDATORY-GROUPS {
			eriChangeIPAddressEventGroup,
			eriChangeIPAddressEventContentGroup
                     }

    ::= { eriChangeIPAddressMIBCompliances 2 }

END
